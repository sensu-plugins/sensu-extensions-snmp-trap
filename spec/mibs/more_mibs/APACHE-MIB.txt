APACHE-MIB DEFINITIONS ::= BEGIN
	-- the imports
	IMPORTS ;

	-- The assignments

    apacheMIB MODULE-IDENTITY
        LAST-UPDATED "9810010000Z"
        ORGANIZATION "Harrie hazewinkel"
        CONTACT-INFO
                "Harrie Hazewinkel

                email: harrie.hazewinkel@jrc.it"
        DESCRIPTION
                "This APACHE-MIB module contains application specific
                managed objects for the Apache HTTP-server."
        REVISION "9810010000Z"
        DESCRIPTION
                "The intial version."
        ::= { enterprises 4 }

jointResearchCentre OBJECT IDENTIFIER ::= { enterprises 1847 }
jrcMIBs OBJECT IDENTIFIER ::= { jointResearchCentre 1 }

    ApacheServerStatusType ::= TEXTUAL-CONVENTION
        STATUS  current
        DESCRIPTION
                "The ApacheServerStatusType defines the types
                for a server."
        SYNTAX  INTEGER {
                        dead(1), starting(2), ready(3), read(4),
                        write(5), keepalive(6), log(7), dns(8), graceful(9)
                }


apacheMIBObjects OBJECT IDENTIFIER ::= { apacheMIB 1 }

    apScoreBoardTable OBJECT-TYPE
        SYNTAX          SEQUENCE OF ApScoreBoardEntry
        MAX-ACCESS      not-accessible
        STATUS          current
        DESCRIPTION
                "This table maintains managed objects for
                the scoreboard."
        ::= { apacheMIBObjects 1 }

    apScoreBoardEntry OBJECT-TYPE
        SYNTAX          ApScoreBoardEntry
        MAX-ACCESS      not-accessible
        STATUS          current
        DESCRIPTION
                "The ApScoreBoardEntry."
        INDEX { apScoreBoardIndex }
        ::= { apScoreBoardTable 1 }

    ApScoreBoardEntry ::=
        SEQUENCE {
                apScoreBoardIndex       Unsigned32,
                apScoreBoardProcessId   Unsigned32,
                apScoreBoardStatus      ApacheServerStatusType,
                apScoreBoardStartTime   TimeStamp,
                apScoreBoardAccessCount Unsigned32,
                apScoreBoardAccessBytes Unsigned32,
                apScoreBoardClient      DisplayString,
                apScoreBoardRequest     DisplayString,
                apScoreBoardVirtualHost Unsigned32
        }

    apScoreBoardIndex OBJECT-TYPE
        SYNTAX          Unsigned32
        MAX-ACCESS      not-accessible
        STATUS          current
        DESCRIPTION
                "The scoreboard index of the servers maintained
                in this running Apache HTTP-server."
        ::= { apScoreBoardEntry 1 }

    apScoreBoardProcessId OBJECT-TYPE
        SYNTAX          Unsigned32
        MAX-ACCESS      read-only
        STATUS          current
        DESCRIPTION
                "The ProcessID of the server."
        ::= { apScoreBoardEntry 2 }

    apScoreBoardStatus OBJECT-TYPE
        SYNTAX          ApacheServerStatusType
        MAX-ACCESS      read-only
        STATUS          current
        DESCRIPTION
                "The status of the server."
        ::= { apScoreBoardEntry 3 }

    apScoreBoardStartTime OBJECT-TYPE
        SYNTAX          TimeStamp
        MAX-ACCESS      read-only
        STATUS          current
        DESCRIPTION
                "The timestamp of when this server became active."
        ::= { apScoreBoardEntry 4 }

    apScoreBoardAccessCount OBJECT-TYPE
        SYNTAX          Unsigned32
        MAX-ACCESS      read-only
        STATUS          current
        DESCRIPTION
                "The number of accesses handled by this server."
        ::= { apScoreBoardEntry 5 }

    apScoreBoardAccessBytes OBJECT-TYPE
        SYNTAX          Unsigned32
        MAX-ACCESS      read-only
        STATUS          current
        DESCRIPTION
                "The number of bytes responded by this server."
        ::= { apScoreBoardEntry 6 }

    apScoreBoardClient OBJECT-TYPE
        SYNTAX          DisplayString
        MAX-ACCESS      read-only
        STATUS          current
        DESCRIPTION
                "The client that is connected to the server."
        ::= { apScoreBoardEntry 7 }

    apScoreBoardRequest OBJECT-TYPE
        SYNTAX          DisplayString
        MAX-ACCESS      read-only
        STATUS          current
        DESCRIPTION
                "The request that the client did."
        ::= { apScoreBoardEntry 8 }

    apScoreBoardVirtualHost OBJECT-TYPE
        SYNTAX          Unsigned32
        MAX-ACCESS      read-only
        STATUS          current
        DESCRIPTION
                "The virtual host being access at the server."
        ::= { apScoreBoardEntry 9 }

    apMIBConformance OBJECT IDENTIFIER ::= { apacheMIB 2 }
    apMIBCompliances OBJECT IDENTIFIER ::= { apMIBConformance 1 }
    apMIBGroups OBJECT IDENTIFIER ::= { apMIBConformance 2 }

    apScoreBoardGroup OBJECT-GROUP
        OBJECTS {
                apScoreBoardProcessId,
                apScoreBoardStatus,
                apScoreBoardStartTime,
                apScoreBoardAccessCount,
                apScoreBoardAccessBytes,
                apScoreBoardClient,
                apScoreBoardRequest,
                apScoreBoardVirtualHost
        }
       STATUS      current
       DESCRIPTION
                ""
       ::= { apMIBGroups 1 }

END
